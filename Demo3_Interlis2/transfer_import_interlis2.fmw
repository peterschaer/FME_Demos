FME workspace transfer_import_interlis2.fmw
Startup Python:
      # -*- coding: latin-1 -*-
      import fmeobjects
      import cx_Oracle
      import os
      import glob

      #=======================================================================================
      # Mehrsprachige Felder in INTERLIS2 behandeln
      def processMultilangFields(feature):

          multilangFields = feature.getAttribute('multilangfields').split(",")

          for mlField in multilangFields:
              content_de = ""
              content_fr = ""
              content_it = ""

              att_Language_list = feature.getAttribute(mlField + '{0}.localizedText{}.Language')
              att_Text_list = feature.getAttribute(mlField + '{0}.localizedText{}.Text')

              # wenn das Multilang-Feld nicht abgefüllt ist, soll es nicht bearbeitet werden
              if att_Language_list is not None:

                      for i in range(len(att_Language_list)):
                          if att_Language_list[i]=="de":
                              content_de = att_Text_list[i]
                          if att_Language_list[i]=="fr":
                              content_fr = att_Text_list[i]
                          if att_Language_list[i]=="it":
                              content_it = att_Text_list[i]

                      # Wenn der Text nur in einer Sprache vorhanden ist, wird er auch für die andere Sprache verwendet
                      if content_de == "":
                          content_de = content_fr
                      if content_de == "":
                          content_de = content_it
                      if content_fr == "":
                          content_fr = content_de
                      if content_fr == "":
                          content_fr = content_it

              feature.setAttribute(mlField + "_DE", content_de)
              feature.setAttribute(mlField + "_FR", content_fr)

      #=======================================================================================
      # Liefereinheit aus fme_dataset extrahieren
      def processLiefereinheit(feature):
          dataset = feature.getAttribute("fme_dataset")
          liefereinheit = os.path.splitext(os.path.basename(dataset))[0]
          feature.setAttribute("LIEFEREINHEIT", liefereinheit)

      #=======================================================================================
      # Liefereinheit(en) löschen
      oraUser = FME_MacroValues["TARGET_USERNAME"]
      oraPW = FME_MacroValues["TARGET_PASSWORD"]
      oraDB = FME_MacroValues["TARGET_ORACLEDB"]
      importDir = FME_MacroValues["IMPORTDIR"]

      def deleteLiefereinheiten(sqlLE):
          inClause = " (" + ",".join(sqlLiefereinheiten) + ")"
          connection = cx_Oracle.connect(oraUser, oraPW, oraDB)
          cursor = connection.cursor()
          queries = [
              "DELETE FROM OEREB.AMT WHERE AMT_LIEFEREINHEIT IN" + inClause,
              "DELETE FROM OEREB.ARTIKEL WHERE ART_LIEFEREINHEIT IN" + inClause,
              "DELETE FROM OEREB.DARSTELLUNGSDIENST WHERE DAR_LIEFEREINHEIT IN" + inClause,
              "DELETE FROM OEREB.EIGENTUMSBESCHRAENKUNG WHERE EIB_LIEFEREINHEIT IN" + inClause,
              "DELETE FROM OEREB.FLAECHE WHERE FLA_LIEFEREINHEIT IN" + inClause,
              "DELETE FROM OEREB.GRUVER WHERE GRV_LIEFEREINHEIT IN" + inClause,
              "DELETE FROM OEREB.HINDEF WHERE HID_LIEFEREINHEIT IN" + inClause,
              "DELETE FROM OEREB.HINDEFVOR WHERE HDV_LIEFEREINHEIT IN" + inClause,
              "DELETE FROM OEREB.HINVOR WHERE HIV_LIEFEREINHEIT IN" + inClause,
              "DELETE FROM OEREB.HINWEIDOK WHERE HWD_LIEFEREINHEIT IN" + inClause,
              "DELETE FROM OEREB.LINIE WHERE LIN_LIEFEREINHEIT IN" + inClause,
              "DELETE FROM OEREB.PUNKT WHERE PUN_LIEFEREINHEIT IN" + inClause,
              "DELETE FROM OEREB.VORSCHRIFT WHERE VOR_LIEFEREINHEIT IN" + inClause
          ]

          for query in queries:
              print query
              cursor.execute(query)
          connection.commit()
          del cursor
          del connection

      print "Folgende Files stehen zum Import an: \n"
      importFiles = glob.glob(importDir + r"\*.xtf")
      sqlLiefereinheiten = []
      if len(importFiles) > 0:
          for f in importFiles:
              print "importiert wird: " + f
              liefereinheit = os.path.splitext(os.path.basename(f))[0]
              sqlLiefereinheiten.append(liefereinheit)
          deleteLiefereinheiten(sqlLiefereinheiten)

Parameters:
- TARGET_ORACLEDB = @(#var.TARGET.DB)   # Oracle-Instanz
- TARGET_USERNAME = @(#var.TARGET.USERNAME)   # OEREB-Username
- TARGET_PASSWORD = @(#var.TARGET.PASSWORD)   # OEREB-Passwort
- TARGET_INSTANCENAME = @(#var.TARGET.SERVICE)   # InstanceName
- MODELLABLAGE = @(#var.INTERLIS.MODELLABLAGE)   # Modellablage
- ORACLE_DB = @(#var.ORACLE.DB)   # Oracle-DB
- ORACLE_OEREB_USERNAME = @(#var.ORACLE.OEREB_USERNAME)   # Oracle-Username
- ORACLE_OEREB_PASSWORD = @(#var.ORACLE.OEREB_PASSWORD)   # Oracle-Passwort
- IMPORTDIR = @(#var.IMPORTDIR)   # Import-Verzeichnis
- INPUT_INTERLIS2 = return FME_MacroValues['IMPORTDIR'] + r"\*.xtf"   # Python Script

Readers:
- ch.ehi.fme.Main_1: ch.ehi.fme.Main from $(INPUT_INTERLIS2)

Writers:
- GEODATABASE_SDE_1: GEODATABASE_SDE to sde
- ORACLE8I_DB_1: ORACLE8I_DB to $(TARGET_ORACLEDB)

Note: OeREBKRM09vs.Vorschriften.Amt
OeREBKRM09vs.Vorschriften.Amt (reader ch.ehi.fme.Main_1)
    attributes: xtf_id xtf_char(200), Name{}.xtf_class, Name{}.localizedText{}.xtf_class, Name{}.localizedText{}.Language xtf_char(255), Name{}.localizedText{}.Text xtf_buffer, AmtImWeb xtf_char(1023)
    -> AMT
AMT
    AttributeRemover_3_OUTPUT_236 -> AttributeRemover_9
    AttributeRemover_3_OUTPUT_236 -> OEREB.AMT (writer ORACLE8I_DB_1)
Note: OEREB.AMT
OEREB.AMT (writer ORACLE8I_DB_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(4,0)
AttributeRemover_9
    REMOVE_ATTRS = AMT_AMTIMWEB_DE,AMT_AMTIMWEB_FR,AMT_NAME_DE,AMT_NAME_FR
    -> AttributeRemover_3
    -> AttributeRemover_5
    -> FeatureMerger_4 [input 2]
AttributeRemover_5
    REMOVE_ATTRS = AMT_AMTIMWEB_DE,AMT_AMTIMWEB_FR,AMT_NAME_DE,AMT_NAME_FR
    -> FeatureMerger_3 [input 2]
AttributeRemover_3
    REMOVE_ATTRS = AMT_AMTIMWEB_DE,AMT_AMTIMWEB_FR,AMT_NAME_DE,AMT_NAME_FR
    -> FeatureMerger_10 [input 2]
Note: OeREBKRM09trsfr.Transferstruktur.DarstellungsDienst
OeREBKRM09trsfr.Transferstruktur.DarstellungsDienst (reader ch.ehi.fme.Main_1)
    attributes: xtf_id xtf_char(200), VerweisWMS xtf_char(1023), LegendeImWeb xtf_char(1023)
    -> DARSTELLUNSDIENST
DARSTELLUNSDIENST
    AttributeCopier_OUTPUT_233 -> AttributeRemover_2
    AttributeCopier_OUTPUT_233 -> OEREB.DARSTELLUNGSDIENST (writer ORACLE8I_DB_1)
Note: OEREB.DARSTELLUNGSDIENST
OEREB.DARSTELLUNGSDIENST (writer ORACLE8I_DB_1)
    attributes: DAR_OID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(4,0), DAR_XTF_ID nvarchar(128)
AttributeRemover_2
    REMOVE_ATTRS = DAR_VERWEISWMS_DE,DAR_VERWEISWMS_FR,DAR_LEGENDEIMWEB_DE,DAR_LEGENDEIMWEB_FR,DAR_LIEFEREINHEIT
    -> FeatureMerger_2 [input 2]
Note: OeREBKRM09vs.Vorschriften.Rechtsvorschrift
OeREBKRM09vs.Vorschriften.Rechtsvorschrift (reader ch.ehi.fme.Main_1)
    attributes: xtf_id xtf_char(200), TextImWeb xtf_char(1023), Rechtsstatus xtf_char(255), publiziertAb xtf_date, Titel{}.localizedText{}.Language xtf_char(255), Titel{}.localizedText{}.Text xtf_buffer, OffiziellerTitel{}.localizedText{}.Language xtf_char(255), OffiziellerTitel{}.localizedText{}.Text xtf_buffer, Abkuerzung{}.localizedText{}.Language xtf_char(255), Abkuerzung{}.localizedText{}.Text xtf_buffer, OffizielleNr xtf_char(20), Kanton xtf_char(255), Gemeinde xtf_int32, Dokument xtf_buffer, ZustaendigeStelle xtf_char(200)
    -> RECHTSVORSCHRIFT
Note: OeREBKRM09vs.Vorschriften.Dokument
OeREBKRM09vs.Vorschriften.Dokument (reader ch.ehi.fme.Main_1)
    attributes: xtf_id xtf_char(200), TextImWeb xtf_char(1023), Rechtsstatus xtf_char(255), publiziertAb xtf_date, Titel{}.localizedText{}.Language xtf_char(255), Titel{}.localizedText{}.Text xtf_buffer, OffiziellerTitel{}.localizedText{}.Language xtf_char(255), OffiziellerTitel{}.localizedText{}.Text xtf_buffer, Abkuerzung{}.localizedText{}.Language xtf_char(255), Abkuerzung{}.localizedText{}.Text xtf_buffer, OffizielleNr xtf_char(20), Kanton xtf_char(255), Gemeinde xtf_int32, Dokument xtf_buffer, ZustaendigeStelle xtf_char(200)
    -> RECHTSVORSCHRIFT
RECHTSVORSCHRIFT
    OEREB_ORACLEDB = $(TARGET_ORACLEDB)
    OEREB_PASSWORD = $(TARGET_PASSWORD)
    OEREB_USERNAME = $(TARGET_USERNAME)
    SQLExecutor_7_RESULT_196 -> FeatureMerger_4 [input 1]
FeatureMerger_4
    PROCESS_DUPS = No
    MERGE_TYPE = Attributes Only
    JOIN_KEYS = @Value(ZustaendigeStelle) @Value(AMT_XTF_ID) @Value(VOR_LIEFEREINHEIT) @Value(AMT_LIEFEREINHEIT)
    SUPPLIER_PREFIX_DUMMY = YES
    MERGED -> OEREB.VORSCHRIFT (writer ORACLE8I_DB_1)
    MERGED -> AttributeRemover_10
    DUPLICATE_SUPPLIER -> Terminator_8
Note: OEREB.VORSCHRIFT
OEREB.VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_DOKUMENT blob, VOR_KANTON nvarchar(2), VOR_LIEFEREINHEIT number(4,0), RES_ID number(10,0), BFS_NR number(5,0), VOA_ID number(10,0), AMT_OID nvarchar(128)
AttributeRemover_10
    REMOVE_ATTRS = VOR_TEXTIMWEB_DE,VOR_TEXTIMWEB_FR,VOR_PUBLIZIERTAB,VOR_OFFIZIELLENR,VOR_KANTON,BFS_NR,VOR_DOKUMENT,ZustaendigeStelle,fme_feature_type,VOR_TITEL_DE,VOR_TITEL_FR,VOR_OFFIZIELLERTITEL_DE,VOR_OFFIZIELLERTITEL_FR,VOR_ABKUERZUNG_DE,VOR_ABKUERZUNG_FR,RES_ID,VOA_ID,VOR_LIEFEREINHEIT,AMT_XTF_ID,AMT_OID
    -> FeatureMerger_7 [input 2]
    -> FeatureMerger_9 [input 2]
    -> FeatureMerger_8 [input 2]
Terminator_8
    MESSAGE = Fehler: Duplicate Supplier bei einem FeatureMerger/Join
Note: OeREBKRM09trsfr.Transferstruktur.Eigentumsbeschraenkung
OeREBKRM09trsfr.Transferstruktur.Eigentumsbeschraenkung (reader ch.ehi.fme.Main_1)
    attributes: xtf_id xtf_char(200), Aussage{}.xtf_class xtf_char(74), Aussage{}.localizedText{}.xtf_class xtf_char(74), Aussage{}.localizedText{}.Language xtf_char(255), Aussage{}.localizedText{}.Text xtf_buffer, Thema xtf_char(255), ArtCode xtf_char(40), ArtCodeliste xtf_char(1023), Rechtsstatus xtf_char(255), publiziertAb xtf_date, DarstellungsDienst xtf_char(200), ZustaendigeStelle xtf_char(200)
    -> EIGENTUMSBESCHRAENKUNG
EIGENTUMSBESCHRAENKUNG
    OEREB_ORACLEDB = $(TARGET_ORACLEDB)
    OEREB_PASSWORD = $(TARGET_PASSWORD)
    OEREB_USERNAME = $(TARGET_USERNAME)
    PythonCaller_OUTPUT_55 -> AttributeRemover
    PythonCaller_OUTPUT_55 -> FeatureMerger_2 [input 1]
AttributeRemover
    REMOVE_ATTRS = EIB_ARTCODE,EIB_ARTCODELISTE,EIB_PUBLIZIERTAB,DarstellungsDienst,ZustaendigeStelle,RES_ID,THE_ID,EIB_AUSSAGE_DE,EIB_AUSSAGE_FR,EIB_LIEFEREINHEIT
    -> FeatureMerger [input 2]
Note: Join mit Darstellungsdienst
FeatureMerger_2
    BUILD_INCOMPLETE = No
    PROCESS_DUPS = No
    MERGE_TYPE = Attributes Only
    REFERATTR = DarstellungsDienst
    REFEEATTR = DAR_XTF_ID
    DUPLICATE_SUPPLIER -> Terminator_4
    COMPLETE -> FeatureMerger_10 [input 1]
Note: Join mit Amt
FeatureMerger_10
    PROCESS_DUPS = No
    MERGE_TYPE = Attributes Only
    JOIN_KEYS = @Value(ZustaendigeStelle) @Value(AMT_XTF_ID) @Value(EIB_LIEFEREINHEIT) @Value(AMT_LIEFEREINHEIT)
    SUPPLIER_PREFIX_DUMMY = YES
    MERGED -> AttributeRemover_4
    DUPLICATE_SUPPLIER -> Terminator_5
AttributeRemover_4
    REMOVE_ATTRS = xtf_id,DarstellungsDienst,ZustaendigeStelle,DAR_XTF_ID,AMT_XTF_ID
    -> AttributeRemover_7
    -> AttributeRemover_8
    -> OEREB.EIGENTUMSBESCHRAENKUNG (writer ORACLE8I_DB_1)
Note: OEREB.EIGENTUMSBESCHRAENKUNG
OEREB.EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(4,0), AMT_OID nvarchar(128), DAR_OID nvarchar(128), RES_ID number(10,0), THE_ID number(10,0)
AttributeRemover_8
    REMOVE_ATTRS = EIB_ARTCODE,EIB_ARTCODELISTE,EIB_PUBLIZIERTAB,RES_ID,THE_ID,EIB_AUSSAGE_DE,EIB_AUSSAGE_FR,EIB_LIEFEREINHEIT,DAR_OID,AMT_OID
    -> GRUNDLAGEVERFEINERUNG [input 2]
    -> GRUNDLAGEVERFEINERUNG [input 3]
AttributeRemover_7
    REMOVE_ATTRS = EIB_ARTCODE,EIB_ARTCODELISTE,EIB_PUBLIZIERTAB,RES_ID,THE_ID,EIB_AUSSAGE_DE,EIB_AUSSAGE_FR,EIB_LIEFEREINHEIT,DAR_OID,AMT_OID
    -> FeatureMerger_5 [input 2]
Terminator_5
    MESSAGE = Fehler: Duplicate Supplier bei einem FeatureMerger/Join
Terminator_4
    MESSAGE = Fehler: Duplicate Supplier bei einem FeatureMerger/Join
Note: OeREBKRM09trsfr.Transferstruktur.HinweisDefinition
OeREBKRM09trsfr.Transferstruktur.HinweisDefinition (reader ch.ehi.fme.Main_1)
    attributes: xtf_id xtf_char(200), Thema xtf_char(255), Kanton xtf_char(255), Gemeinde xtf_int32, ZustaendigeStelle xtf_char(200)
    -> SQLExecutor_11
    -> Terminator
Note: Lookup THEMA
SQLExecutor_11 [off]
    ORACLE8I_DB_USER_NAME = $(TARGET_USERNAME)
    ORACLE8I_DB_PASSWORD = $(TARGET_PASSWORD)
    SQL_STATEMENT = select the_id from thema  where lower(the_thema)=lower('@Value(Thema)')
    EXPOSED_ATTRIBUTE_LIST = THE_ID
    ORACLE8I_DB_SERVER_TYPE = ORACLE8i
    DATASET = $(TARGET_ORACLEDB)
    ORACLE8I_DB_REMOVE_SCHEMA_QUALIFIER = NO
    COMBINE_GEOM = Initiator Geometry Only
    COMBINE_ATTRS = Keep Initiator Attributes if Conflict
    FORMAT = ORACLE8I_DB
    RESULT -> OEREB.HINDEF (writer ORACLE8I_DB_1)
Note: OEREB.HINDEF
OEREB.HINDEF (writer ORACLE8I_DB_1) [off]
    attributes: HID_OID nvarchar(128), HID_XTF_ID nvarchar(128), HID_KANTON nvarchar(2), HID_LIEFEREINHEIT number(4,0), AMT_OID nvarchar(128), THE_ID number(10,0), BFS_NR number(5,0)
Note: OeREBKRM09trsfr.Transferstruktur.HinweisDefinitionDokument
OeREBKRM09trsfr.Transferstruktur.HinweisDefinitionDokument (reader ch.ehi.fme.Main_1)
    attributes: xtf_id xtf_char(200), HinweisDefinition xtf_char(200), Dokument xtf_char(200)
    -> SQLExecutor_13
    -> Terminator
Terminator
    MESSAGE = Abbruch: HinweisDefinition gefunden!!!
Note: Diese Association hat keine ID, / deshalb via Sequence
SQLExecutor_13 [off]
    ORACLE8I_DB_USER_NAME = $(TARGET_USERNAME)
    ORACLE8I_DB_PASSWORD = $(TARGET_PASSWORD)
    SQL_STATEMENT = select oereb.oereb_unique_id.nextval UUID_HDV_ID from dual
    EXPOSED_ATTRIBUTE_LIST = UUID_HDV_ID
    ORACLE8I_DB_SERVER_TYPE = ORACLE8i
    DATASET = $(TARGET_ORACLEDB)
    ORACLE8I_DB_REMOVE_SCHEMA_QUALIFIER = NO
    COMBINE_GEOM = Initiator Geometry Only
    COMBINE_ATTRS = Keep Initiator Attributes if Conflict
    FORMAT = ORACLE8I_DB
    RESULT -> OEREB.HINDEFVOR (writer ORACLE8I_DB_1)
Note: OEREB.HINDEFVOR
OEREB.HINDEFVOR (writer ORACLE8I_DB_1) [off]
    attributes: HDV_ID nvarchar(128), HDV_XTF_ID nvarchar(128), HDV_LIEFEREINHEIT number(4,0), VOR_OID nvarchar(128), HID_OID nvarchar(128)
Note: OeREBKRM09vs.Vorschriften.Artikel
OeREBKRM09vs.Vorschriften.Artikel (reader ch.ehi.fme.Main_1)
    attributes: xtf_id xtf_char(200), TextImWeb xtf_char(1023), Rechtsstatus xtf_char(255), publiziertAb xtf_date, Nr xtf_char(20), Text{}.xtf_class, Text{}.localizedText{}.xtf_class, Text{}.localizedText{}.Language xtf_char(255), Text{}.localizedText{}.Text xtf_buffer, Dokument xtf_char(200)
    -> ARTIKEL
Note: Hier fehlt noch der Link zur Rechtsvorschrift / bzw. zum Dokument. Im Beispiel des BAZL / kommt das gar nicht vor.
ARTIKEL
    OEREB_ORACLEDB = $(TARGET_ORACLEDB)
    OEREB_PASSWORD = $(TARGET_PASSWORD)
    OEREB_USERNAME = $(TARGET_USERNAME)
    PythonCaller_4_OUTPUT_255 -> OEREB.ARTIKEL (writer ORACLE8I_DB_1)
Note: OEREB.ARTIKEL
OEREB.ARTIKEL (writer ORACLE8I_DB_1)
    attributes: ART_OID nvarchar(128), ART_XTF_ID nvarchar(128), ART_TEXTIMWEB_DE nvarchar(1023), ART_TEXTIMWEB_FR nvarchar(1023), ART_PUBLIZIERTAB date, ART_NR nvarchar(20), ART_TEXT_DE nclob, ART_TEXT_FR nclob, ART_LIEFEREINHEIT number(4,0), RES_ID number(10,0)
Note: OeREBKRM09trsfr.Transferstruktur.Geometrie
OeREBKRM09trsfr.Transferstruktur.Geometrie (reader ch.ehi.fme.Main_1)
    attributes: xtf_id xtf_char(200), Linie xtf_buffer, Flaeche xtf_buffer, Rechtsstatus xtf_char(255), publiziertAb xtf_date, MetadatenGeobasisdaten xtf_char(1023), Eigentumsbeschraenkung xtf_char(200), ZustaendigeStelle xtf_char(200)
    -> GEOMETRIE
GEOMETRIE
    OEREB_ORACLEDB = $(TARGET_ORACLEDB)
    OEREB_PASSWORD = $(TARGET_PASSWORD)
    OEREB_USERNAME = $(TARGET_USERNAME)
    UUIDGenerator_2_OUTPUT_323 -> FeatureMerger [input 1]
FeatureMerger
    BUILD_INCOMPLETE = No
    PROCESS_DUPS = No
    MERGE_TYPE = Attributes Only
    REFERATTR = Eigentumsbeschraenkung
    REFEEATTR = EIB_XTF_ID
    DUPLICATE_SUPPLIER -> Terminator_2
    COMPLETE -> FeatureMerger_3 [input 1]
FeatureMerger_3
    PROCESS_DUPS = No
    MERGE_TYPE = Attributes Only
    JOIN_KEYS = @Value(ZustaendigeStelle) @Value(AMT_XTF_ID) @Value(LIEFEREINHEIT) @Value(AMT_LIEFEREINHEIT)
    SUPPLIER_PREFIX_DUMMY = YES
    DUPLICATE_SUPPLIER -> Terminator_3
    MERGED -> AttributeRemover_6
AttributeRemover_6
    REMOVE_ATTRS = Eigentumsbeschraenkung,ZustaendigeStelle,EIB_XTF_ID,AMT_XTF_ID
    -> TestFilter
Note: Geometrie filtern
TestFilter
    TEST_LIST = BOOL_OP,OR,COMPOSITE_TEST,<Unused>,TEST_CLAUSE,"TEST ""@Value(fme_type)"" = ""fme_point""",PUNKT,BOOL_OP,OR,COMPOSITE_TEST,<Unused>,TEST_CLAUSE,"TEST ""Flaeche"" NOT_ATTRIBUTE_IS_NULL ""<Unused>""",FLAECHE,BOOL_OP,OR,COMPOSITE_TEST,<Unused>,TEST_CLAUSE,"TEST ""Linie"" NOT_ATTRIBUTE_IS_NULL ""<Unused>""",LINIE
    DEFAULT_VALUE = <UNFILTERED>
    FLAECHE -> GeometryReplacer
    LINIE -> GeometryReplacer_2
    PUNKT -> BulkAttributeRenamer
BulkAttributeRenamer
    REPLACE_STR = PUN_
    ATTRCHOICE = Selected Attributes
    PATTERN_ACTION_DISP = Add String Prefix
    ATTRLIST = XTF_ID PUBLIZIERTAB METAGEO_DE METAGEO_FR OID LIEFEREINHEIT
    -> OEREB.PUNKT (writer GEODATABASE_SDE_1)
Note: OEREB.PUNKT
OEREB.PUNKT (writer GEODATABASE_SDE_1)
    attributes: PUN_OID char(128), PUN_XTF_ID char(128), PUN_PUBLIZIERTAB date, PUN_METAGEO_DE char(1023), PUN_METAGEO_FR char(1023), PUN_LIEFEREINHEIT smallint, EIB_OID char(128), AMT_OID char(128), RES_ID integer
GeometryReplacer
    ATTR = Flaeche
    KIND_LONG = FME Binary
    -> BulkAttributeRenamer_2
BulkAttributeRenamer_2
    REPLACE_STR = FLA_
    ATTRCHOICE = Selected Attributes
    PATTERN_ACTION_DISP = Add String Prefix
    ATTRLIST = XTF_ID PUBLIZIERTAB METAGEO_DE METAGEO_FR OID LIEFEREINHEIT
    -> OEREB.FLAECHE (writer GEODATABASE_SDE_1)
Note: OEREB.FLAECHE
OEREB.FLAECHE (writer GEODATABASE_SDE_1)
    attributes: FLA_OID char(128), FLA_XTF_ID char(128), FLA_PUBLIZIERTAB date, FLA_METAGEO_DE char(1023), FLA_METAGEO_FR char(1023), FLA_LIEFEREINHEIT smallint, EIB_OID char(128), AMT_OID char(128), RES_ID integer
GeometryReplacer_2
    ATTR = Linie
    KIND_LONG = FME Binary
    -> BulkAttributeRenamer_3
BulkAttributeRenamer_3
    REPLACE_STR = LIN_
    ATTRCHOICE = Selected Attributes
    PATTERN_ACTION_DISP = Add String Prefix
    ATTRLIST = XTF_ID PUBLIZIERTAB METAGEO_DE METAGEO_FR OID LIEFEREINHEIT
    -> OEREB.LINIE (writer GEODATABASE_SDE_1)
Note: OEREB.LINIE
OEREB.LINIE (writer GEODATABASE_SDE_1)
    attributes: LIN_OID char(128), LIN_XTF_ID char(128), LIN_PUBLIZIERTAB date, LIN_METAGEO_DE char(1023), LIN_METAGEO_FR char(1023), LIN_LIEFEREINHEIT smallint, EIB_OID char(128), AMT_OID char(128), RES_ID integer
Terminator_3
    MESSAGE = Fehler: Duplicate Supplier bei einem FeatureMerger/Join
Terminator_2
    MESSAGE = Fehler: Duplicate Supplier bei einem FeatureMerger/Join
Note: OeREBKRM09trsfr.Transferstruktur.HinweisVorschrift
OeREBKRM09trsfr.Transferstruktur.HinweisVorschrift (reader ch.ehi.fme.Main_1)
    attributes: xtf_id xtf_char(200), Eigentumsbeschraenkung xtf_char(200), Vorschrift xtf_char(200), ArtikelNr{}.xtf_class xtf_char(74), ArtikelNr{}.value xtf_char(20)
    -> HINWEISVORSCHRIFT
HINWEISVORSCHRIFT
    HINWEISVORSCHRIFT_AttributeRenamer_OUTPUT_212 -> FeatureMerger_5 [input 1]
Note: Join mit Eigentums- / beschränkung
FeatureMerger_5
    BUILD_INCOMPLETE = No
    PROCESS_DUPS = No
    MERGE_TYPE = Attributes Only
    REFERATTR = Eigentumsbeschraenkung
    REFEEATTR = EIB_XTF_ID
    COMPLETE -> FeatureMerger_7 [input 1]
    DUPLICATE_SUPPLIER -> Terminator_6
Note: Join mit Vorschrift
FeatureMerger_7
    BUILD_INCOMPLETE = No
    PROCESS_DUPS = No
    MERGE_TYPE = Attributes Only
    REFERATTR = Vorschrift
    REFEEATTR = VOR_XTF_ID
    COMPLETE -> OEREB.HINVOR (writer ORACLE8I_DB_1)
    DUPLICATE_SUPPLIER -> Terminator_7
Note: OEREB.HINVOR
OEREB.HINVOR (writer ORACLE8I_DB_1)
    attributes: HIV_ID nvarchar(128), HIV_XTF_ID nvarchar(128), HIV_LIEFEREINHEIT number(4,0), EIB_OID nvarchar(128), VOR_OID nvarchar(128), HIV_ARTNR nvarchar(255)
Terminator_7
    MESSAGE = Fehler: Duplicate Supplier bei einem FeatureMerger/Join
Terminator_6
    MESSAGE = Fehler: Duplicate Supplier bei einem FeatureMerger/Join
Note: OeREBKRM09vs.Vorschriften.HinweisWeitereDokumente
OeREBKRM09vs.Vorschriften.HinweisWeitereDokumente (reader ch.ehi.fme.Main_1)
    attributes: xtf_id xtf_char(200), Ursprung xtf_char(200), Hinweis xtf_char(200), ArtikelNr{}.xtf_class, ArtikelNr{}.value xtf_char(20)
    -> HINWEIDOK
HINWEIDOK
    UUIDGenerator_OUTPUT_184 -> FeatureMerger_9 [input 1]
Note: Ursprung joinen
FeatureMerger_9
    PROCESS_DUPS = No
    MERGE_TYPE = Attributes Only
    JOIN_KEYS = @Value(Ursprung) @Value(VOR_XTF_ID)
    MERGED -> AttributeRenamer
    DUPLICATE_SUPPLIER -> Terminator_10
AttributeRenamer
    ATTR_LIST = VOR_OID,VOR_OIDURSPRUNG,""
    -> AttributeRemover_11
AttributeRemover_11
    REMOVE_ATTRS = Ursprung,VOR_XTF_ID
    -> FeatureMerger_8 [input 1]
Note: Hinweis joinen. Hinweise (gesetzliche Grundlagen) / können auch ausserhalb des ITFs liegen). Deshalb / muss auch der NOT_MERGED-Ausgang bearbeitet werden.
FeatureMerger_8
    PROCESS_DUPS = No
    MERGE_TYPE = Attributes Only
    JOIN_KEYS = @Value(Hinweis) @Value(VOR_XTF_ID)
    MERGED -> AttributeRenamer_2
    NOT_MERGED -> AttributeRenamer_3
    DUPLICATE_SUPPLIER -> Terminator_9
AttributeRenamer_2
    ATTR_LIST = VOR_OID,VOR_OIDHINWEIS,""
    -> AttributeRemover_12
AttributeRemover_12
    REMOVE_ATTRS = Hinweis,VOR_XTF_ID
    -> OEREB.HINWEIDOK (writer ORACLE8I_DB_1)
AttributeRenamer_3
    ATTR_LIST = Hinweis,VOR_OIDHINWEIS,""
    -> OEREB.HINWEIDOK (writer ORACLE8I_DB_1)
Note: OEREB.HINWEIDOK
OEREB.HINWEIDOK (writer ORACLE8I_DB_1)
    attributes: HWD_ID nvarchar(128), HWD_XTF_ID nvarchar(128), HWD_LIEFEREINHEIT number(4,0), VOR_OIDURSPRUNG nvarchar(128), VOR_OIDHINWEIS nvarchar(128), HWD_ARTNR nvarchar(255)
Terminator_9
    MESSAGE = Fehler: Duplicate Supplier bei einem FeatureMerger/Join
Terminator_10
    MESSAGE = Fehler: Duplicate Supplier bei einem FeatureMerger/Join
Note: OeREBKRM09trsfr.Transferstruktur.GrundlageVerfeinerung
OeREBKRM09trsfr.Transferstruktur.GrundlageVerfeinerung (reader ch.ehi.fme.Main_1)
    attributes: xtf_id xtf_char(200), Grundlage xtf_char(200), Verfeinerung xtf_char(200)
    -> GRUNDLAGEVERFEINERUNG [input 1]
GRUNDLAGEVERFEINERUNG
    AttributeRenamer_OUTPUT_341 -> OEREB.GRUVER (writer ORACLE8I_DB_1)
Note: OEREB.GRUVER
OEREB.GRUVER (writer ORACLE8I_DB_1)
    attributes: GRV_ID number(10,0), GRV_XTF_ID nvarchar(128), GRV_LIEFEREINHEIT number(4,0), EIB_OIDGRUNDLAGE nvarchar(128), EIB_OIDVERFEINERUNG nvarchar(128)
Note: XTF_TRANSFER
XTF_TRANSFER (reader ch.ehi.fme.Main_1) [off]
    attributes: oidspace{}.name xtf_char(255), oidspace{}.oiddomain xtf_char(255), comment xtf_char(255)
Note: XTF_BASKETS
XTF_BASKETS (reader ch.ehi.fme.Main_1) [off]
    attributes: xtf_topic, xtf_id xtf_char(200), xtf_startstate xtf_char(250), xtf_endstate xtf_char(250)
Note: XTF_DELETEOBJECT
XTF_DELETEOBJECT (reader ch.ehi.fme.Main_1) [off]
    attributes: xtf_id xtf_char(200)

FME custom transformer EIGENTUMSBESCHRAENKUNG

Parameters:
- OEREB_ORACLEDB = teamt   # Oracle-Instanz
- OEREB_USERNAME = oereb   # OEREB-Username
- OEREB_PASSWORD = green$8851   # OEREB-Passwort

SQLExecutor_2_INITIATOR_61 (input)
    -> SQLExecutor_2
Note: Lookup RECHTSSTATUS
SQLExecutor_2
    ORACLE8I_DB_USER_NAME = $(OEREB_USERNAME)
    ORACLE8I_DB_PASSWORD = $(OEREB_PASSWORD)
    SQL_STATEMENT = select res_id from rechtsstatus where lower(res_rechtsstatus)=lower('@Value(Rechtsstatus)')
    EXPOSED_ATTRIBUTE_LIST = RES_ID
    ORACLE8I_DB_SERVER_TYPE = ORACLE8i
    DATASET = $(OEREB_ORACLEDB)
    ORACLE8I_DB_REMOVE_SCHEMA_QUALIFIER = NO
    COMBINE_GEOM = Initiator Geometry Only
    COMBINE_ATTRS = Keep Initiator Attributes if Conflict
    FORMAT = ORACLE8I_DB
    RESULT -> SQLExecutor
Note: Lookup THEMA
SQLExecutor
    ORACLE8I_DB_USER_NAME = $(OEREB_USERNAME)
    ORACLE8I_DB_PASSWORD = $(OEREB_PASSWORD)
    SQL_STATEMENT = select the_id from thema  where lower(the_thema)=lower('@Value(Thema)')
    EXPOSED_ATTRIBUTE_LIST = THE_ID
    ORACLE8I_DB_SERVER_TYPE = ORACLE8i
    DATASET = $(OEREB_ORACLEDB)
    ORACLE8I_DB_REMOVE_SCHEMA_QUALIFIER = NO
    COMBINE_GEOM = Initiator Geometry Only
    COMBINE_ATTRS = Keep Initiator Attributes if Conflict
    FORMAT = ORACLE8I_DB
    RESULT -> DateFormatter
Note: publiziertAb / formatieren
DateFormatter
    DATE_ATTR = publiziertAb
    FMT = FME Date (%Y%m%d)
    -> UUIDGenerator
Note: Neue UUID generieren
UUIDGenerator
    UUID_ATTR = _uuid
    -> AttributeCreator
Note: Mehrsprachige Felder / deklarieren
AttributeCreator
    ATTR_LIST = multilangfields,Aussage
    -> PythonCaller
Note: Mehrsprachiger Text / verarbeiten
PythonCaller
    PYTHONSYMBOL = processMultilangFields
    NEW_ATTRIBUTES = Aussage_DE Aussage_FR
    -> AttributeRemover
Note: Überflüssige Attribute entfernen
AttributeRemover
    LIST_ATTRS = Aussage{}.localizedText{}.Text Aussage{}.localizedText{}.xtf_class Aussage{}.localizedText{}.Language Aussage{}.localizedText{} Aussage{}.xtf_class Aussage{}
    REMOVE_ATTRS = Thema,Rechtsstatus,multilangfields
    -> AttributeRenamer
Note: "Richtige" Attributnamen vergeben
AttributeRenamer
    ATTR_LIST = ArtCode,EIB_ARTCODE,"",ArtCodeliste,EIB_ARTCODELISTE,"",Aussage_DE,EIB_AUSSAGE_DE,"",Aussage_FR,EIB_AUSSAGE_FR,"",publiziertAb,EIB_PUBLIZIERTAB,"",_uuid,EIB_OID,"",xtf_id,EIB_XTF_ID,""
    -> PythonCaller_2
Note: Liefereinheit setzen
PythonCaller_2
    PYTHONSYMBOL = processLiefereinheit
    NEW_ATTRIBUTES = LIEFEREINHEIT
    -> AttributeRenamer_2
Note: Liefereinheit setzen
AttributeRenamer_2
    ATTR_LIST = LIEFEREINHEIT,EIB_LIEFEREINHEIT,""
    -> PythonCaller_OUTPUT_55 (output)
PythonCaller_OUTPUT_55 (output)

FME custom transformer GEOMETRIE

Parameters:
- OEREB_ORACLEDB = teamt   # Oracle-Instanz
- OEREB_USERNAME = oereb   # OEREB-Username
- OEREB_PASSWORD = green$8851   # OEREB-Passwort

DateFormatter_2_INPUT_99 (input)
    -> DateFormatter_2
Note: publiziertAb / formatieren
DateFormatter_2
    DATE_ATTR = publiziertAb
    FMT = FME Date (%Y%m%d)
    -> SQLExecutor_3
Note: Lookup RECHTSSTATUS
SQLExecutor_3
    ORACLE8I_DB_USER_NAME = $(OEREB_USERNAME)
    ORACLE8I_DB_PASSWORD = $(OEREB_PASSWORD)
    SQL_STATEMENT = select res_id from rechtsstatus where lower(res_rechtsstatus)=lower('@Value(Rechtsstatus)')
    EXPOSED_ATTRIBUTE_LIST = RES_ID
    ORACLE8I_DB_SERVER_TYPE = ORACLE8i
    DATASET = $(OEREB_ORACLEDB)
    ORACLE8I_DB_REMOVE_SCHEMA_QUALIFIER = NO
    COMBINE_GEOM = Initiator Geometry Only
    COMBINE_ATTRS = Keep Initiator Attributes if Conflict
    FORMAT = ORACLE8I_DB
    RESULT -> AttributeExposer
Note: fme_type
AttributeExposer
    ATTR_LIST = fme_type
    -> UUIDGenerator_2
UUIDGenerator_2
    UUID_ATTR = OID
    -> AttributeRenamer
AttributeRenamer
    ATTR_LIST = publiziertAb,PUBLIZIERTAB,"",MetadatenGeobasisdaten,METAGEO_DE,"",xtf_id,XTF_ID,""
    -> AttributeCopier
AttributeCopier
    ATTR_LIST = METAGEO_FR,METAGEO_DE
    -> AttributeRemover
AttributeRemover
    REMOVE_ATTRS = Rechtsstatus
    -> PythonCaller
Note: Liefereinheit setzen
PythonCaller
    PYTHONSYMBOL = processLiefereinheit
    NEW_ATTRIBUTES = LIEFEREINHEIT
    -> UUIDGenerator_2_OUTPUT_323 (output)
UUIDGenerator_2_OUTPUT_323 (output)

FME custom transformer DARSTELLUNSDIENST

UUIDGenerator_INPUT_349 (input)
    -> UUIDGenerator
Note: UUID generieren
UUIDGenerator
    UUID_ATTR = _uuid
    -> AttributeRenamer_2
Note: Attribute umbenennen
AttributeRenamer_2
    ATTR_LIST = LegendeImWeb,DAR_LEGENDEIMWEB_DE,"",VerweisWMS,DAR_VERWEISWMS_DE,"",_uuid,DAR_OID,"",xtf_id,DAR_XTF_ID,""
    -> AttributeCopier
Note: URL auch ins franz. Feld abfüllen
AttributeCopier
    ATTR_LIST = DAR_LEGENDEIMWEB_FR,DAR_LEGENDEIMWEB_DE,DAR_VERWEISWMS_FR,DAR_VERWEISWMS_DE
    -> PythonCaller_2
Note: Liefereinheit setzen
PythonCaller_2
    PYTHONSYMBOL = processLiefereinheit
    NEW_ATTRIBUTES = LIEFEREINHEIT
    -> AttributeRenamer_3
Note: Liefereinheit setzen
AttributeRenamer_3
    ATTR_LIST = LIEFEREINHEIT,DAR_LIEFEREINHEIT,""
    -> AttributeCopier_OUTPUT_233 (output)
AttributeCopier_OUTPUT_233 (output)

FME custom transformer ARTIKEL

Parameters:
- OEREB_ORACLEDB = teamt   # Oracle-Instanz
- OEREB_USERNAME = oereb   # OEREB-Username
- OEREB_PASSWORD = green$8851   # OEREB-Passwort

SQLExecutor_8_INITIATOR_245 (input)
    -> SQLExecutor_8
Note: Lookup RECHTSSTATUS
SQLExecutor_8
    ORACLE8I_DB_USER_NAME = $(OEREB_USERNAME)
    ORACLE8I_DB_PASSWORD = $(OEREB_PASSWORD)
    SQL_STATEMENT = select res_id from rechtsstatus where lower(res_rechtsstatus)=lower('@Value(Rechtsstatus)')
    EXPOSED_ATTRIBUTE_LIST = RES_ID
    ORACLE8I_DB_SERVER_TYPE = ORACLE8i
    DATASET = $(OEREB_ORACLEDB)
    ORACLE8I_DB_REMOVE_SCHEMA_QUALIFIER = NO
    ORACLE8I_DB_PERSISTENT_CONNECTION = YES
    COMBINE_GEOM = Initiator Geometry Only
    COMBINE_ATTRS = Keep Initiator Attributes if Conflict
    FORMAT = ORACLE8I_DB
    RESULT -> DateFormatter_4
Note: publiziertAb / formatieren
DateFormatter_4
    DATE_ATTR = publiziertAb
    FMT = FME Date (%Y%m%d)
    -> AttributeCreator_4
Note: Mehrsprachige Felder / deklarieren
AttributeCreator_4
    ATTR_LIST = multilangfields,Text
    -> PythonCaller_4
Note: Mehrsprachiger Text / verarbeiten
PythonCaller_4
    PYTHONSYMBOL = processMultilangFields
    NEW_ATTRIBUTES = Text_DE Text_FR
    -> AttributeCreator
AttributeCreator
    ATTR_LIST = ART_TEXTIMWEB_FR,@Value(TextImWeb)
    -> UUIDGenerator
UUIDGenerator
    UUID_ATTR = ART_OID
    -> PythonCaller_3
Note: Liefereinheit setzen
PythonCaller_3
    PYTHONSYMBOL = processLiefereinheit
    NEW_ATTRIBUTES = LIEFEREINHEIT
    -> AttributeRenamer_2
Note: Liefereinheit setzen
AttributeRenamer_2
    ATTR_LIST = LIEFEREINHEIT,ART_LIEFEREINHEIT,""
    -> AttributeRenamer
AttributeRenamer
    ATTR_LIST = publiziertAb,ART_PUBLIZIERTAB,"",TextImWeb,ART_TEXTIMWEB_DE,"",Nr,ART_NR,"",Text_DE,ART_TEXT_DE,"",Text_FR,ART_TEXT_FR,"",xtf_id,ART_XTF_ID,""
    -> AttributeRemover
AttributeRemover
    LIST_ATTRS = Text{}.localizedText{}.Text Text{} Text{}.localizedText{} Text{}.localizedText{}.Language Text{}.xtf_class Text{}.localizedText{}.xtf_class
    REMOVE_ATTRS = Rechtsstatus,Dokument,multilangfields
    -> PythonCaller_4_OUTPUT_255 (output)
PythonCaller_4_OUTPUT_255 (output)

FME custom transformer HINWEIDOK

UUIDGenerator_INPUT_184 (input)
    -> UUIDGenerator
Note: Association hat keine ID, / deshalb wird UUID erzeugt
UUIDGenerator
    UUID_ATTR = HWD_ID
    -> ListConcatenator
Note: ArtikelNr in ein Feld / konkatenieren
ListConcatenator
    VAL_ATTR = HWD_ARTNR
    SEP = ,
    LIST_ATTR = ArtikelNr{}.value
    DROP_EMPTY_PARTS = No
    -> AttributeRenamer
AttributeRenamer
    ATTR_LIST = xtf_id,HWD_XTF_ID,""
    -> PythonCaller_2
Note: Liefereinheit setzen
PythonCaller_2
    PYTHONSYMBOL = processLiefereinheit
    NEW_ATTRIBUTES = LIEFEREINHEIT
    -> AttributeRenamer_2
Note: Liefereinheit setzen
AttributeRenamer_2
    ATTR_LIST = LIEFEREINHEIT,HWD_LIEFEREINHEIT,""
    -> AttributeRemover
AttributeRemover
    LIST_ATTRS = ArtikelNr{} ArtikelNr{}.value ArtikelNr{}.xtf_class
    -> UUIDGenerator_OUTPUT_184 (output)
UUIDGenerator_OUTPUT_184 (output)

FME custom transformer GRUNDLAGEVERFEINERUNG

UUIDGenerator_INPUT_222 (input)
    -> UUIDGenerator
UUIDGenerator
    UUID_ATTR = GRV_ID
    -> FeatureMerger_6 [input 1]
FeatureMerger_6_SUPPLIER_237 (input)
    -> FeatureMerger_6 [input 2]
FeatureMerger_6
    BUILD_INCOMPLETE = No
    PROCESS_DUPS = No
    MERGE_TYPE = Attributes Only
    REFERATTR = Grundlage
    REFEEATTR = EIB_XTF_ID
    COMPLETE -> AttributeCopier
AttributeCopier
    ATTR_LIST = EIB_OIDGRUNDLAGE,EIB_OID
    -> AttributeRemover_9
AttributeRemover_9
    REMOVE_ATTRS = Grundlage,EIB_XTF_ID,EIB_OID
    -> FeatureMerger_7 [input 1]
FeatureMerger_7_SUPPLIER_312 (input)
    -> FeatureMerger_7 [input 2]
FeatureMerger_7
    BUILD_INCOMPLETE = No
    PROCESS_DUPS = No
    MERGE_TYPE = Attributes Only
    REFERATTR = Verfeinerung
    REFEEATTR = EIB_XTF_ID
    COMPLETE -> AttributeRenamer
    DUPLICATE_SUPPLIER -> Terminator_6
AttributeRenamer
    ATTR_LIST = EIB_OID,EIB_OIDVERFEINERUNG,"",xtf_id,GRV_XTF_ID,""
    -> PythonCaller_2
Note: Liefereinheit setzen
PythonCaller_2
    PYTHONSYMBOL = processLiefereinheit
    NEW_ATTRIBUTES = LIEFEREINHEIT
    -> AttributeRenamer_2
Note: Liefereinheit setzen
AttributeRenamer_2
    ATTR_LIST = LIEFEREINHEIT,GRV_LIEFEREINHEIT,""
    -> AttributeRenamer_OUTPUT_341 (output)
AttributeRenamer_OUTPUT_341 (output)
Terminator_6
    MESSAGE = Fehler: Duplicate Supplier bei einem FeatureMerger/Join

FME custom transformer AMT

AttributeCreator_2_INPUT_184 (input)
    -> AttributeCreator_2
Note: Mehrsprachige Felder / deklarieren
AttributeCreator_2
    ATTR_LIST = multilangfields,Name
    -> PythonCaller_2
Note: Mehrsprachiger Text / verarbeiten
PythonCaller_2
    PYTHONSYMBOL = processMultilangFields
    NEW_ATTRIBUTES = Name_DE Name_FR
    -> AttributeRenamer
Note: Attribute umbenennen
AttributeRenamer
    ATTR_LIST = Name_DE,AMT_NAME_DE,"",Name_FR,AMT_NAME_FR,"",AmtImWeb,AMT_AMTIMWEB_DE,"",xtf_id,AMT_XTF_ID,""
    -> AttributeCopier
Note: dt. URL in die franz. URL
AttributeCopier
    ATTR_LIST = AMT_AMTIMWEB_FR,AMT_AMTIMWEB_DE
    -> UUIDGenerator
UUIDGenerator
    UUID_ATTR = AMT_OID
    -> AttributeRemover_3
Note: Unnötige Attribute / entfernen
AttributeRemover_3
    LIST_ATTRS = Name{}.localizedText{}.Language Name{}.xtf_class Name{}.localizedText{} Name{}.localizedText{}.xtf_class Name{}.localizedText{}.Text Name{}
    REMOVE_ATTRS = multilangfields
    -> PythonCaller_3
Note: Liefereinheit setzen
PythonCaller_3
    PYTHONSYMBOL = processLiefereinheit
    NEW_ATTRIBUTES = LIEFEREINHEIT
    -> AttributeRenamer_2
Note: Liefereinheit setzen
AttributeRenamer_2
    ATTR_LIST = LIEFEREINHEIT,AMT_LIEFEREINHEIT,""
    -> AttributeRemover_3_OUTPUT_236 (output)
AttributeRemover_3_OUTPUT_236 (output)

FME custom transformer HINWEISVORSCHRIFT

HINWEISVORSCHRIFT_UUIDGenerator_INPUT_220 (input)
    -> UUIDGenerator_2
UUIDGenerator_2
    UUID_ATTR = HIV_ID
    -> ListConcatenator
Note: ArtikelNummer in ein / Feld konkatenieren
ListConcatenator
    VAL_ATTR = HIV_ARTNR
    SEP = ,
    LIST_ATTR = ArtikelNr{}.value
    DROP_EMPTY_PARTS = No
    -> AttributeRenamer_2
AttributeRenamer_2
    ATTR_LIST = xtf_id,HIV_XTF_ID,""
    -> AttributeRemover
AttributeRemover
    LIST_ATTRS = ArtikelNr{} ArtikelNr{}.value ArtikelNr{}.xtf_class
    -> PythonCaller_2
Note: Liefereinheit setzen
PythonCaller_2
    PYTHONSYMBOL = processLiefereinheit
    NEW_ATTRIBUTES = LIEFEREINHEIT
    -> AttributeRenamer_3
Note: Liefereinheit setzen
AttributeRenamer_3
    ATTR_LIST = LIEFEREINHEIT,HIV_LIEFEREINHEIT,""
    -> HINWEISVORSCHRIFT_AttributeRenamer_OUTPUT_212 (output)
HINWEISVORSCHRIFT_AttributeRenamer_OUTPUT_212 (output)

FME custom transformer RECHTSVORSCHRIFT

Parameters:
- OEREB_ORACLEDB = teamt   # Oracle-Instanz
- OEREB_USERNAME = oereb   # OEREB-Username
- OEREB_PASSWORD = green$8851   # OEREB-Passwort

AttributeCreator_3_INPUT_192 (input)
    -> AttributeCreator_3
Note: Mehrsprachige Felder / deklarieren
AttributeCreator_3
    ATTR_LIST = multilangfields,Titel,Abkuerzung,OffiziellerTitel
    -> PythonCaller_3
Note: Mehrsprachiger Text / verarbeiten
PythonCaller_3
    PYTHONSYMBOL = processMultilangFields
    NEW_ATTRIBUTES = Titel_DE Titel_FR OffiziellerTitel_DE OffiziellerTitel_FR Abkuerzung_DE Abkuerzung_FR
    -> SQLExecutor_6
Note: Lookup RECHTSSTATUS
SQLExecutor_6
    ORACLE8I_DB_USER_NAME = $(OEREB_USERNAME)
    ORACLE8I_DB_PASSWORD = $(OEREB_PASSWORD)
    SQL_STATEMENT = select res_id from rechtsstatus where lower(res_rechtsstatus)=lower('@Value(Rechtsstatus)')
    EXPOSED_ATTRIBUTE_LIST = RES_ID
    ORACLE8I_DB_SERVER_TYPE = ORACLE8i
    DATASET = $(OEREB_ORACLEDB)
    ORACLE8I_DB_REMOVE_SCHEMA_QUALIFIER = NO
    COMBINE_GEOM = Initiator Geometry Only
    COMBINE_ATTRS = Keep Initiator Attributes if Conflict
    FORMAT = ORACLE8I_DB
    RESULT -> DateFormatter_3
Note: publiziertAb / formatieren
DateFormatter_3
    DATE_ATTR = publiziertAb
    FMT = FME Date (%Y%m%d)
    -> AttributeValueMapper
Note: Vorschriftsart setzen / (REVO oder HINW) je / nach FeatureType
AttributeValueMapper
    DIRECTION = Forward (Source To Destination)
    VAL_ATTR = VOA_ID
    DEFAULT_VALUE = -99
    LUT = OeREBKRM09vs.Vorschriften.Dokument,3,OeREBKRM09vs.Vorschriften.Rechtsvorschrift,1
    SRC = fme_feature_type
    -> UUIDGenerator
UUIDGenerator
    UUID_ATTR = VOR_OID
    -> AttributeRenamer
AttributeRenamer
    ATTR_LIST = xtf_id,VOR_XTF_ID,"",TextImWeb,VOR_TEXTIMWEB_DE,"",publiziertAb,VOR_PUBLIZIERTAB,"",Titel_DE,VOR_TITEL_DE,"",Titel_FR,VOR_TITEL_FR,"",OffiziellerTitel_DE,VOR_OFFIZIELLERTITEL_DE,"",OffiziellerTitel_FR,VOR_OFFIZIELLERTITEL_FR,"",Abkuerzung_DE,VOR_ABKUERZUNG_DE,"",Abkuerzung_FR,VOR_ABKUERZUNG_FR,"",OffizielleNr,VOR_OFFIZIELLENR,"",Dokument,VOR_DOKUMENT,"",Kanton,VOR_KANTON,"",Gemeinde,BFS_NR,""
    -> AttributeCopier
AttributeCopier
    ATTR_LIST = VOR_TEXTIMWEB_FR,VOR_TEXTIMWEB_DE
    -> AttributeRemover
AttributeRemover
    LIST_ATTRS = Abkuerzung{}.localizedText{}.Text Titel{} Abkuerzung{}.localizedText{}.Language Abkuerzung{}.localizedText{} Titel{}.localizedText{}.xtf_class OffiziellerTitel{} OffiziellerTitel{}.xtf_class OffiziellerTitel{}.localizedText{}.Text Titel{}.localizedText{} Abkuerzung{}.xtf_class Titel{}.localizedText{}.Language OffiziellerTitel{}.localizedText{} OffiziellerTitel{}.localizedText{}.xtf_class Titel{}.localizedText{}.Text Titel{}.xtf_class OffiziellerTitel{}.localizedText{}.Language Abkuerzung{}.localizedText{}.xtf_class Abkuerzung{}
    REMOVE_ATTRS = Rechtsstatus,multilangfields
    -> PythonCaller_2
Note: Liefereinheit setzen
PythonCaller_2
    PYTHONSYMBOL = processLiefereinheit
    NEW_ATTRIBUTES = LIEFEREINHEIT
    -> AttributeRenamer_2
Note: Liefereinheit setzen
AttributeRenamer_2
    ATTR_LIST = LIEFEREINHEIT,VOR_LIEFEREINHEIT,""
    -> SQLExecutor_7_RESULT_196 (output)
SQLExecutor_7_RESULT_196 (output)
