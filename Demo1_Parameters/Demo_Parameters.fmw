FME workspace Demo_Parameters.fmw

Parameters:
- BFSNR = 733   # BFS-Nummer
- SPATIALITE_DB = bauinv.sqlite   # Source SpatiaLite Database File(s)
- CSVFILE = bfsnr.csv   # CSV-File
- SHAPEDIR = .   # Destination Esri Shape Directory

Readers:
- SPATIALITE_1: SPATIALITE from $(SPATIALITE_DB)

Writers:
- SHAPE_1: SHAPE to $(SHAPEDIR)

Note: Bauinventar (Spatialite)
geodb_bauinv_bauinv (reader SPATIALITE_1)
    attributes: url string(255), nummer string(255), plz integer, k_objekt string(255), baugruppe1 string(255), code integer, baugruppe3 string(255), gemeinde string(255), strasse string(255), begid integer, bfs integer, baugruppe2 string(255), io_id integer, koord_y integer, ort string(255), status string(255), koord_x integer
    -> TestFilter
Note: Gewünschte Gemeinde per / BFS-Nummer herausfiltern
TestFilter
    TEST_LIST = BOOL_OP,OR,COMPOSITE_TEST,<Unused>,TEST_CLAUSE,"TEST @Value(bfs) = $(BFSNR)",BFSFILTER
    DEFAULT_VALUE = <UNFILTERED>
    BFSFILTER -> BFS (writer SHAPE_1)
Note: Gemeinde-Shapefile
BFS (writer SHAPE_1)
    attributes: url char(255), nummer char(255), plz number(11,0), k_objekt char(255), baugruppe1 char(255), code number(11,0), baugruppe3 char(255), gemeinde char(255), strasse char(255), begid number(11,0), bfs number(11,0), baugruppe2 char(255), io_id number(11,0), koord_y number(11,0), ort char(255), status char(255), koord_x number(11,0)
